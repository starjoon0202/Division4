module service-function-scheduler-type {

  namespace "urn:intel:params:xml:ns:yang:sfc-sfst";

  prefix sfc-sfst;

  import ietf-yang-types {
      prefix yang;
      revision-date 2010-09-24;
}

  organization "Intel, Inc.";
  contact "Johnson Li <johnson.li@intel.com>";


  description
    "This module contains a collection of YANG definitions for
     managing service function scheduler types.";

  revision 2015-03-12 {
    description
      "Initial version.";
    reference "https://tools.ietf.org/html/draft-penno-sfc-yang";
  }

  // Service Function Scheduler Type
  identity service-function-scheduler-type-identity {
    description
      "Base identity from which specific service function
       scheduler types are derived.";
  }

  identity icps{
    base "service-function-scheduler-type-identity";
    description "iCPS Scheduler.";
  }

  identity random {
    base "service-function-scheduler-type-identity";
    description "Random Scheduler.";
  }

  identity round-robin {
    base "service-function-scheduler-type-identity";
    description "Round Robin.";
  }

  identity shortest-path {
    base "service-function-scheduler-type-identity";
    description "Shortest Path.";
  }

  identity load-balance {
    base "service-function-scheduler-type-identity";
    description "Load Balance.";
  }

  identity weighted-shortest-path {
    base "service-function-scheduler-type-identity";
    description "Weighted Shortest Path.";
  }

  identity user-defined {
    base "service-function-scheduler-type-identity";
    description "User Defined Scheduler Type.";
  }

  typedef service-function-scheduler-type {
    type identityref {
      base "service-function-scheduler-type-identity";
    }
    description "This type is used to reference all
      registered service function scheduler types";
  }

  container service-function-scheduler-types {
    description
      "A list of Service function scheduler types. For each type we
       keep a list of service function scheduler names. Each name may
       indicate the vendor of the scheduler";

    list service-function-scheduler-type {
      key "type";
      leaf type {
        type service-function-scheduler-type;
        description
            "The service function scheduler type";
      }
      leaf enabled {
        type boolean;
        description
            "The enabled status of this scheduler type.";
      }
      leaf name {
        type string;
        description
          "The name of the service function schedule type.";
      }

      description
        "A list of all service function schedule types.";
    }
  }
}
